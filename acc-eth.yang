module acc-eth {
    yang-version 1.1;
    namespace "urn:ccsa:yang:acc-eth";
    prefix acc-eth;
    import ietf-yang-types {
        prefix yang;
    }
    import acc-yang-types {
         prefix acc-type; 
    }
    
    import acc-devm {
        prefix acc-devm;
    }
    
    import acc-connection {
        prefix acc-con;
    }

    import acc-otn {
        prefix acc-otn;
    }

    import acc-enum {
        prefix acc-enum;
    }

    import acc-protection-group {
        prefix acc-pg;
    }

    revision 2020-02-09 {
        description "remove useless grouping eth-nni";
    }

    /*
   * common types
   */
    identity ETH {
        base acc-type:layer-protocol-name;
    }
   
    typedef oam-transmit-interval {
        type enumeration {
            enum interval-3ms33 {
                value 1;
                description "3.33ms";
            }
            enum interval-10ms {
                value 2;
                description "10ms";
            }
            enum interval-100ms {
                value 3;
                description "100ms";
            }
            enum interval-1s {
                value 4;
                description "1s";
            }
            enum interval-10s {
                value 5;
                description "10s";
            }
            enum interval-1min {
                value 6;
                description "1min";
            }
        }
        description "oam transmit interval";
    }
    

        typedef port-type {
        type enumeration {
            enum electrical {
                value 0;
            }
            enum optical {
                value 1;
            }
        }
        description "none";
    }
    typedef working-mode {
        type enumeration {
            enum auto {
                value 0;
            }
            enum 100MFullDuplex {
                value 1;
            }
            enum 1000MFullDuplex {
                value 2;
            }
            enum 10GEFullDuplex {
                value 3;
            }
        }
    }

    

    typedef eth-mapping-type {
        type enumeration {
            enum EoO {
                value 0;
                description "Ethernet over OTN.";
            }
            enum EoS {
                value 1;
                description "Ethernet over SDH.";
            }
        }
    }

    /*
   * groupings
   */
    

    grouping eth-ftp-pac {
        leaf supported-mtu {
            mandatory true;
            type uint64;
            config false;
        }
        leaf current-mtu {
            mandatory true;
            type uint64;
        }
        leaf service-mapping-mode {
            mandatory true;
            type acc-enum:adaptation-type;
        }
        leaf mapping-type {
            mandatory true;
            type eth-mapping-type;
        }
    }

    augment "/acc-devm:ptps/acc-devm:ptp" {
        container eth-mapping-pac {
            leaf-list supported-mapping-type {
                config false;
                type eth-mapping-type;
                description "EoO,EoS  1..*";
            }
            leaf-list supported-odu-server-switch-capability {
                config false;
                type acc-enum:odu-switch-type;
                description "ODU能力上报，支持什么就上报什么";
            }
            leaf-list supported-sdh-server-switch-capability {
                config false;
                type acc-enum:sdh-switch-type;
                description "SDH能力上报，支持什么就上报什么";
            }
        }
    }

    augment "/acc-devm:ptps/acc-devm:ptp" {
        when "acc-devm:layer-protocol-name = 'ETH'";
        container eth-ptp-pac {
            leaf-list supported-working-mode {
                type working-mode;
                config false;
            }

            leaf current-working-mode {
                mandatory true;
                type working-mode;
            }
            leaf supported-mtu {
                mandatory true;
                type uint64;
                config false;
            }
            leaf current-mtu {
                mandatory true;
                type uint64;
            }
            leaf pause-control {
                mandatory true;
                type boolean;
            }
            leaf mac-address {
                type yang:mac-address;
            }
            leaf port-type {
                mandatory true;
                type port-type;
                config false;
            }
            leaf lldp-enable {
                type boolean;
            }
            leaf lldp-peer-chassis-id {
                config false;
                type string {
                    length 1..255;
                }
            }
            leaf lldp-peer-port-id {
                config false;
                type string {
                    length 1..255;
                }
                description "hex ascii number without 0x，not normal string";
            }
            leaf lldp-peer-system-name {
                config false;
                type string {
                    length 1..64;
                }
            }
        }
        
        
	
	    
    }

    augment "/acc-devm:ftps/acc-devm:ftp" {
        when "acc-devm:layer-protocol-name = 'ETH'";
        container eth-ftp-pac {
            uses eth-ftp-pac;
        }
    }

    augment "/acc-devm:ctps/acc-devm:ctp" {
        when "acc-devm:layer-protocol-name = 'ETH'";
        container eth-ctp-pac {
            container vlan-spec {
                uses acc-con:vlan-spec;
                description "vlan spec";
            }
            container client-vlan-spec {
                uses acc-con:vlan-spec;
                description "client vlan spec";
            }
            container performance {
                leaf delay {
                    mandatory true;
                    type uint64;
                    description "delay";
                }
                leaf near-packet-loss-rate {
                    mandatory true;
                    type acc-type:real;
                    description "near packet loss rate";
                }
                leaf far-packet-loss-rate {
                    mandatory true;
                    type acc-type:real;
                    description "far packet loss rate";
                }
                leaf tx-bytes {
                    mandatory true;
                    type uint64;
                    description "tx bytes";
                }
                leaf rx-bytes {
                    mandatory true;
                    type uint64;
                    description "rx bytes";
                }
                config false;
            }
            container oam-state-pac {
                leaf dm-state {
                    mandatory true;
                    type boolean;
                    description "dm state";
                }
                leaf tm-state {
                    mandatory true;
                    type boolean;
                    description "tm state";
                }
                leaf lm-state {
                    mandatory true;
                    type boolean;
                    description "lm state";
                }
                leaf cc-state {
                    mandatory true;
                    type boolean;
                    description "cc state";
                }
                description "802.1ag test state";
            }
            container oam-config {
                leaf mep-id {
                    mandatory true;
                    type uint16 {
                        range "1..8191";
                    }
                }
                leaf remote-mep-id {
                    mandatory true;
                    type uint16 {
                        range "1..8191";
                    }
                }
                leaf meg-id {
                    mandatory true;
                    type string;
                }
                leaf md-name {
                    mandatory true;
                    type string {
                        length "1..43";
                    }
                }
                leaf mel {
                    mandatory true;
                    type uint8 {
                        range "0..7";
                    }
                }
                leaf cc-interval {
                    mandatory true;
                    type oam-transmit-interval;
                    description "cv transmit period :3.33ms/10ms/100ms/1s/10s/1min";
                }
                leaf lm-interval {
                    mandatory true;
                    type oam-transmit-interval;
                    description "lm transmit period :1s/10s/1min";
                }
                leaf dm-interval {
                    mandatory true;
                    type oam-transmit-interval;
                    description "dm transmit period :1s/10s/1min";
                }
                description "ethernet oam parameters: mep id, meg id, mel, cc interval, etc";
            }
        }
    }

    notification lldp-change-notification {
        leaf ptp-name {
            mandatory true;
            type string {
                length 1..64;
            }
            description
                "PTP name.";
        }
        leaf lldp-peer-chassis-id {
              mandatory true;
            type string {
                length 1..64;
            }
        }
        leaf lldp-peer-port-id {
              mandatory true;
            type string {
                length 1..64;
            }
        }
        leaf lldp-peer-system-name {
              mandatory true;
            type string {
                length 1..64;
            }
        }
        description "LLDP change notification";
    }

    rpc create-eth-connection {
        input {
            uses acc-con:create-connection;
            leaf service-mapping-mode {
                type acc-enum:adaptation-type;
            }
            leaf uni-protection-type {
                type acc-pg:protection-type;
                description "default lag";
            }
            leaf nni-protection-type {
                type acc-pg:protection-type;
            }
            leaf nni2-protection-type {
                type acc-pg:protection-type;
            }
            container eth-uni {
                leaf uni-ptp-name {
                    type string;
                }
                leaf second-uni-ptp-name {
                    type string;
                }
                container client-vlan-spec {
		          when "../../service-type = 'EVPL'";
                    uses acc-con:vlan-spec;
                    description "只适用于EVPL，指定C-VLAN，用于客户Vlan与运营商Vlan的匹配，无需携带accessAction。不携带该参数时表示端口匹配";
                }
                container uni-vlan-spec {
                    when "../../service-type = 'EVPL'";
                    uses acc-con:vlan-spec;
                    description "只适用于EVPL，可选。用于在客户VLAN交换的情况下，指定C-VLAN的交换值，accessAction=KEEP(默认)，exchange";
                }
            }

            container primary-nni {
                uses acc-otn:nni;
                container ftp-vlan-spec {
                    uses acc-con:vlan-spec;
                    description "EVPL必须下发，对于其它业务可选。对于UNI-NNI业务， accessAction=PUSH_POP， 对于NNI-NNI则 pushpop or exchange";
                }
                description "primary nni,必选";
            }
            container secondary-nni {
                uses acc-otn:nni;
                container ftp-vlan-spec {
                    uses acc-con:vlan-spec;
                    description "EVPL必须下发，对于其它业务可选,对于UNI-NNI业务， accessAction=PUSH_POP";
                }
                description "ETH带保护模式，可选";
            }
            container primary-nni2 {
                uses acc-otn:nni;
                container ftp-vlan-spec {
                    uses acc-con:vlan-spec;
                    description "EVPL必须下发，对于其它业务可选。对于NNI-NNI业务，accessAction=KEEP或EXCHANGE";
                }
                description "NNI-NNI不带保护，可选";
            }
            container secondary-nni2 {
                uses acc-otn:nni;
                container ftp-vlan-spec {
                    uses acc-con:vlan-spec;
                    description "EVPL必须下发，对于其它业务可选,对于NNI-NNI业务，accessAction=KEEP或EXCHANGE";
                }
                description "NNI-NNI带保护，可选";
            }
        }
        output {
            container connection {
                uses acc-con:connection;
            }
            container create-component {
                leaf-list ftp-name {
                    type string {
                        length "1..64";
                    }
                }
                leaf-list ctp-name {
                    type string {
                        length "1..64";
                    }
                }                
            }
        }
    }
}
